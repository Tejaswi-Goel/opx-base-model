module system-status {

    namespace "http://www.dellemc.com/networking/os10/system-status";

    prefix "system-status";

    import dell-yang-types {
      prefix common;
    }

    organization "Dell EMC";

    contact "http://www.dell.com/support";

    description
         "This module contains YANG definition for system status, which provides an overall system
          status as well as individual sensor details such as usage, threshold, and fault states.

          Copyright (c) 2015-2018 by Dell EMC, All rights reserved.";

    revision 2018-12-05{
        description "Changed attr name from 'name' to 'proc-name' to solve disambiguation issue";
        reference "Network Platform Abstraction";
    }

    revision 2018-10-31{
        description "Added attributes for obtaining process info of running processes";
        reference "Network Platform Abstraction";
    }

    revision 2018-08-17{
        description "Fixing pyang IETF errors and adding documentiation to the model.";
        reference "Network Platform Abstraction";	
    }

    revision "2017-11-07" {
  	description "Add node id attribute to current status. ";
        reference "Network Platform Abstraction";	
    }

    revision "2017-09-18" {
  	description "Initial version.";
        reference "Network Platform Abstraction";	
    }

	typedef status-levels {
		type enumeration {
			enum RED {
			    value 1;
				description "System's fault status is Red.";
			}
			enum YELLOW {
			    value 2;
				description "System's fault status is Yellow.";
			}
			enum GREEN {
			    value 3;
				description "System's status is Green - no fault.";
			}
		}
                description "Possible values of the status.";
	}
	typedef sensor-type {
		type enumeration {
			enum CPU { value 1; }
			enum DISK { value 2; }
			enum FAN { value 3; }
			enum MEM { value 4; }
			enum POWER { value 5; }
			enum SWAP { value 6; }
			enum TEMPERATURE { value 7; }
		}
		description "This type lists available sensors in the system";
	}


	typedef sensor-value-type {
		type enumeration {
			enum INT { value 1; }
			enum FLOAT { value 2; }
			enum STRING { value 3; }
		}
		description "This describes the data type of the value that sensor provides";
	}

	container current-status {
		leaf status {
		        type status-levels;
		        config false;
		        description "The status field represents overall system status which considers all sensors
		                    including CPU, disk, memory, temperature, fan and other system events. Events will be
		                    sent out when the status changes and this field can be queried.";
		}

		leaf node-id {
			type string;
			config false;
			description "This is the name to uniquely identify a node.";
		}

        list process-info {
            key "param-type rank";
    
            leaf proc-name {
                type string;
                config false;
                description "This is the process name";
            }
            leaf pid {
                type uint32;
                config false;
                description "This is the process ID";
            }
            leaf param-type {
                type sensor-type;
                config false;
                description "This is the type of process parameter being measured";
            }
            leaf usage-percent {
                type common:xfloat;
                config false;
                description "This is the usage percentage of the specified process parameter type";
            }
            leaf rank {
                type uint32;
                config false;
                description "This is the usage rank, as compared with other processes. Highest usage is 1, while lower usages are in increasing order";
            }
            description "A list of processes and their info";
        }

		list sensor {

			key "name";

			leaf name {
			     type sensor-type;
		             config false;
			     description "This is the name of the sensor included in the overall health status,
			                 e.g. CPU, disk, memory, swap, fan, power, temperature, etc.";
			}

			leaf description {
			     type string;
		             config false;
			     description "This is an indication of the sensor name, value, and default threshold information.";
			}

			leaf value-type {
			     type sensor-value-type;
		             config false;
			     description "The type of the value and threshold fields.  It is up to the back end service
			                  and application to determine the correct parsing logic based on the type specified.";
			}

			leaf value {
			     type string;
		             config false;
			     description "This is the performance/status data of the sensor, e.g. fan speed, CPU usage,
		                          free disk/memory/swap space, etc. This value is of string type and its numeric type is
			                  described in value-type attribute";
			}

			leaf threshold {
			     type string;
			     description "This is an optional threshold. The fault state of a sensor is triggered from false
			                  to true when the value of the sensor goes above or below the threshold, depending on the
			                  sensor type (e.g. fault is triggered when fan speed goes lower than its threshold, or CPU usage
			                  exceeds its threshold, etc.). This value is of string type and its numeric type is described in
			                  value-type attribute.";
			}
			
			leaf fault-state {
			     type boolean;
		             config false;
			     description "Indicates if the threshold value has been activated.";
			}
			description "This is the list of sensors that go into the current status field.  This list
				can be checked independently of the overall current-status/status field.";

		}
                description "Set of attributes defining the overall system status. It includes the individual
                             sensor statuses.";
	}
}
