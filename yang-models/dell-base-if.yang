module dell-base-if-common {
    namespace "http://www.dellemc.com/networking/os10/base/dell-base-if-common";

    prefix "dell-base-if-cmn";

    import ietf-interfaces {
        prefix "if";
    }
    import ietf-yang-types {
        prefix "yang";
    }
    import dell-base-common {
        prefix "base-cmn";
    }

    import dell-interface {
        prefix "dell-if";
    }
    organization "Dell EMC";
    contact "http://www.dell.com/support";

    description "This model augments the standard interface model and adds DellEMC
                 specific attributes and/or RPCs to it.

                 Copyright (c) 2015-2018 by Dell EMC, All rights reserved.";

    revision "2018-11-19" {
         description "Add Enumeration for UPDATE in the member-op.";
         reference "Network Platform Abstraction";
     }
    revision "2018-10-03" {
         description "Added parameters in get-mac-address rpc to support application based
                      MAC address retrieval.";
         reference "Network Platform Abstraction";
    }

    revision "2018-09-07" {
         description "Adding front-panel-port id and subport-id into the interface state object.";
         reference "Network Platform Abstraction";
     }

    revision "2018-08-10" {
        description "Fixing pyang IETF errors and adding documentation to the model.";
        reference "Network Platform Abstraction";
    }

    revision "2018-05-08" {
        description "Added support for VLAN filtering object. This object helps to
                     get or set VLAN filtering feature on an interface";
        reference "Network Platform Abstraction";
    }

    revision "2018-01-22" {
        description "Augmented if/interfaces model from dell-interface to handle the
                     attributes augmented in dell-interface.yang";
        reference "Network Platform Abstraction";
    }

    revision "2017-10-10" {
        description "Add typedef for update type to use it for leaf list attribute type.
                     Add member-op attribute for rpc set-interface to handle leaf-list update";
        reference "Network Platform Abstraction";
    }

    revision "2016-01-01" {
        description "Initial version.";
        reference "Network Platform Abstraction";
    }


    augment "/if:interfaces/if:interface" {

        leaf if-index {
            type base-cmn:logical-ifindex;
            description "Unique ID used for identifying a physical or logical interface.";
        }

        leaf vlan-filter {
            type base-cmn:filter-type;
            default "INGRESS_ENABLE";
            description "Flag used for enabling or disabling VLAN filtering on an interface.
                         By default, Ingress VLAN Filter is enabled";
        }
        description "Including DellEMC specific interface attributes that are common to all interface types.";
    }

    augment "/if:interfaces-state/if:interface" {

        leaf vlan-filter {
            type base-cmn:filter-type;
            description "Used to get the status of Interface VLAN filtering flag";
        }

        leaf front-panel-port {
            type uint32;
            description "ID of front-panel-port (Indexed from 1 to max front panel port).";
        }

        leaf-list subport-id {
            type uint32;
            description "Physical lane on which hardware port exists.";
        }
        description "Including DellEMC specific interface-state attributes that are common to all interface types";
    }

    augment "/if:interfaces-state/if:interface/if:statistics" {

        leaf time-stamp{
            type yang:timestamp;
            description "Timestamp at which stats are returned";
        }
        description "Including DellEMC specific interface-counter attributes that are common to all interface types.";
    }

    typedef operation-type {

        type enumeration {
            enum CREATE {
                value 1;
                description "Operation to create interface";
            }
            enum DELETE {
                value 2;
                description "Operation to delete interface";
            }
            enum UPDATE {
                value 3;
                description "Operation to update interface attributes";
            }
        }
        description "Types of operations performed during interface configuration";

    }
    typedef update-type {
        type enumeration {
            enum ADD {
                value 1;
                description "Operation to add member";
            }
            enum REMOVE {
                value 2;
                description "Operation to remove member";
            }
            enum UPDATE {
                value 3;
                description "Operation to change the properties of membership";
            }
        }
        description "Types of operations performed while updating interface configuration";
    }

    // LAG specfic
    augment "/if:interfaces/if:interface" {
        when "if:type = 'ianaift:ieee8023adLag'";

        list member-ports {
          key "name";
          leaf name {
            type if:interface-ref;
            must "/if:interfaces/if:interface[if:name = current()]"
             +   "/if:type = 'ianaift:ethernetCsmacd'" {
              error-message
                "Only Ethernet interfaces can be added as member ports to a port-channel!";
            }
            description "interface name";
          }
          description
                "This has member interfaces";
        }
        description "This extension is focused on LAG attributes.";
    }

    rpc set-interface {

        description "This method is used to create, delete or set multiple types of interface. For
                create operation, MAC address will be allocated if it is not given within input argument.
                Currently there is only one input argument which specified operation type, user should
                use attributes of the model of corresponding interface type as extra input.
                if:interface model is used as input for interface configuration.";
        // QUALIFIER  :  target
        // ========
        //
        // OBJ PATH : dell-base-if-cmn/set-interface
        // ========
        //
        // INPUT  :
        // =====
        // a) Explicit:
        //    --------
        //              dell-base-if-cmn/set-interface/input/operation (1=create, 2=delete, 3=update),
        //              dell-base-if-cmn/set-interface/input/member-op (1=add, 2=remove),
        // b) Implicit:
        //    --------
        //    Users could use additional attributes from other models (eg. if, base-if-phy etc.)
        //    Eg.
        //            	if/interfaces/interface/name,
        //             	if/interfaces/interface/type,
        //             	if/interfaces/interface/enabled,
        //             	if/interfaces/interface/mtu,
        //             	if/interfaces/interface/learn-mode,
        //             	if/interfaces/interface/tagging-mode(For Phy Interface Only),
        //             	if/interfaces/interface/speed(For Phy Interface Only),
        //             	if/interfaces/interface/auto-negotiation(For Phy Interface Only),
        //             	if/interfaces/interface/duplex(For Phy Interface Only),
        //             	if/interfaces/interface/eee(For Phy Interface Only),
        //             	if/interfaces/interface/fec(For Phy Interface Only),
        //             	if/interfaces/interface/oui(For Phy Interface Only),
        //             	if/interfaces/interface/type(For Phy Interface Only),
        //              Etc.
        // OUTPUT :
        // ======
        // a) Explicit:
        //    --------
        //	        None.
        // b) Implicit:
        //    -------
        //              dell-base-if-cmn/if/interfaces/interface/if-index.

        input {
            leaf operation {
                type operation-type;
                description "Specify operation type to configure interface.";
            }
            leaf member-op {
                type update-type;
                description " Specify the operation type in case of member add or remove. This field is optional
                              and member list is considered a complete list in case if member-op is not present.";
            }
        }
    }

    rpc get-mac-address {
        description "This method is used to get assgined MAC address for different type of interfaces.
                User should give required attributes such as interface-name, type as input. The actual
                attributes needed depends on requested interface type.";

        // QUALIFIER  :  target
        // ========
        //
        // OBJ PATH : dell-base-if-cmn/get-mac-address
        // ========
        //
        // INPUT  :
        // =====
        // Default:
        //    --------
        //    Users could use additional attributes from other models (eg. if, base-if-phy etc.)
        //    Eg.
        //              base-if-phy/hardware-port/front-panel-port (For "interface" application and "front-panel" type)
        //              base-if-phy/hardware-port/subport-id (For "interface" application and "front-panel" type)
        //              base-if-vlan/if/interfaces/interface/id (For "interface" application and "vlan" type)
        //              if/interfaces/interface/name (For "interface" application and "lag" type)
        // OUTPUT :
        // ======
        // Default:
        //    -------
        //              dell-if/if/interfaces/interface/phys-address.

        // Function specification :
        // ======================
        // This RPC method is implemented as internal service to allocate MAC addresses for front-panel,
        // VLAN and LAG interfaces, as well as reserve MAC address being used in specific domain like FCoE
        // and VxLAN management. The reserved MAC address range of multiple domains is defined in platform
        // dependent configuration file. User could ask for allocated MAC address by giving application and type
        // along with optional offset value (by default is 0) corresponding to different domain.

        input {
            leaf application {
                type string;
                default "interface";
                description "Specify the name of application for assigned MAC address to be read. MAC address
                             pool for each application is defined at platform dependent configuration file. If
                             configuration file uses old format and there is no application based MAC address
                             pool specified, the MAC address ranges inside are treat as under interface
                             application.";
            }

            leaf type {
                type string;
                description "Specify the type name of MAC address pool to be used.";
            }

            leaf offset {
                type uint32;
                default 0;
                description "Specify the offset value of MAC address to be read in MAC address pool.";
            }
        }

        output {
            leaf number-of-mac-addresses {
                type uint32;
                description "Give total number of MAC addresses allocated to specified application.";
            }
        }
    }

    augment "/dell-if:clear-counters/dell-if:input" {
        description "Adding attributes to the input parameter of dell-if/clear-counters RPC";

    }

    augment "/dell-if:clear-eee-counters/dell-if:input" {
        description "Adding attributes to the input parameter of dell-if/clear-eee-counters RPC";

    }

    augment "/if:interfaces"{
        description "Adding nodes to the standard interface model";

    }
}
